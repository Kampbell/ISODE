-- Module MhsMTAAsn1Module (X.467:10/1996)
-- See also ITU-T X.467 (10/1996)
-- See also the index of all ASN.1 assignments needed in this document


MhsMTAAsn1Module {joint-iso-itu-t mhs(6) management(9) mta(8) modules(8)
  asn1-module(1)} DEFINITIONS IMPLICIT TAGS ::=
BEGIN

--	Prologue
--	Exports everything
IMPORTS
  --	MTS abstract service parameters
  ContentIntegrityCheck, ContentLength, ContentType, Credentials,
    EncodedInformationTypes, ExplicitConversion, GlobalDomainIdentifier,
    MessageOriginAuthenticationCheck, MessageToken, MTAName, MTSIdentifier,
    Operations, ORAddress, OriginatorCertificate, ORName, Password, Priority,
    ProbeOriginAuthenticationCheck, ProofOfDelivery, ProofOfDeliveryRequest,
    PSAPAddress, RecipientCertificate, ReportingMTACertificate,
    ReportOriginAuthenticationCheck, RequestedDeliveryMethod, Restriction,
    SecurityContext, SecurityLabel, StrongCredentials, Time
    FROM MTSAbstractService {joint-iso-itu-t mhs(6) mts(3) modules(0)
      mts-abstract-service(1) version-1999(1)}
  --	AuthenticationFramework parameters
  AlgorithmIdentifier
    FROM AuthenticationFramework {joint-iso-itu-t ds(5) module(1)
      authenticationFramework(7) 3}
  --	InformationFramework parameters
  Name, DistinguishedName
    FROM InformationFramework {joint-iso-itu-t ds(5) module(1)
      informationFramework(1) 3};

--	Supporting productions
ApplicationContext ::= OBJECT IDENTIFIER

ApplicationContexts ::= SET OF ApplicationContext

AssociationInitiator ::= INTEGER {local(0), remote(1)}

BilateralDeferral ::= INTEGER {agreement(0), no-agreement(1)}

Colocated ::= BOOLEAN --	colocated is true, remote is false

ContentTypes ::= SET OF ContentType

DurationInSeconds ::= INTEGER

EMailAccessPointAddress ::= CHOICE {
  psap            [0]  PSAPAddress,
  genericAddress  [1]  GenericAddress
}

--	The genericAddress encoding may be used for non-standardised access point addresses. The description of
--	the use of this generic type is beyond the scope of this Recommendation | International Standard.
EMailContentType ::=
  ContentType

EmailContentTypes ::= SET OF EMailContentType

EMailConversionType ::= CHOICE {
  x400Conversion     [0]  ExplicitConversion,
  genericConversion  [1]  GenericConversion
}

--	The genericConversion type encoding may be used for the description of non-standardised conversion
--	types. The description of the use of this generic type is beyond the scope of this
--	Recommendation | International Standard.
EMailCredentials ::= CHOICE {
  simple  EMailSimpleCredentials,
  strong  EMailStrongCredentials
}

EMailDirectoryName ::= CHOICE {
  x500DirectoryName  [0]  Name,
  genericNames       [1]  SET OF GenericName
}

--	The genericNames encoding may be used for the description of non X.500 directory access. The description of
--	the use of this generic type is beyond the scope of this Recommendation | International Standard.
EMailEits ::= CHOICE {
  x400EIT      [0]  EncodedInformationTypes,
  genericEITs  [1]  SEQUENCE OF OBJECT IDENTIFIER
}

--	The genericEITs encoding may be used for the description of non-standardised EITs. The description of
--	the use of this generic type is beyond the scope of this Recommendation | International Standard.
EMailGlobalDomainId ::= CHOICE {
  x400GlobalDomainId     [0]  GlobalDomainIdentifier,
  genericGlobalDomainId  [1]  GenericName
}

--	The genericGlobalDomainId encoding may be used for the description of non-standardised global domain
--	identifiers. The description of the use of this generic type is beyond the scope of this
--	Recommendation | International Standard.
EMailMpduIdentifier ::= CHOICE {
  x400MTSIdentifier      [0]  MTSIdentifier,
  genericMpduIdentifier  [1]  GenericMessageId
}

--	The genericMpduIdentifier encoding may be used for the description of non-standardised MPDU identifier.
--	The description of the use of this generic type is beyond the scope of this
--	Recommendation | International Standard.
EMailMtaName ::= CHOICE {
  x400MTAName     [0]  MTAName,
  genericMTAName  [1]  GenericName
}

--	The genericMTAName encoding may be used for the description of non-standardised MTA names.
--	The description of the use of this generic type is beyond the scope of this
--	Recommendation | International Standard.
EMailMtsUserName ::= CHOICE {
  x400ORName   [0]  ORName,
  genericName  [1]  GenericName
}

--	The genericName encoding may be used for the description of non-standardised MTs User name. The description 
--	of the use of this generic type is beyond the scope of this Recommendation | International Standard.
EMailMtsUserNames ::= SET OF EMailMtsUserName

EMailRedirections ::= SET {
  label    Label,
  address  CHOICE {none        NULL,
                   email-addr  EMailMtsUserName}
}

Label ::= INTEGER

EMailSimpleCredentials ::= Password

EMailStrongCredentials ::= CHOICE {
  x400StrongCredentials     [0]  StrongCredentials,
  genericStrongCredentials  [1]  GenericStrongCredentials
}

--	The genericStrongCredentials encoding may be used for the description of non-standardised credentials.
--	The description of the use of this generic type is beyond the scope of this
--	Recommendation | International Standard.
GenericAddress ::= SEQUENCE {displayFormat  IA5String,
                             typedFormat    EXTERNAL
}

--	The allocation of the Object Identifier values related to the EXTERNAL type is beyond the scope of this
--	 Recommendation | International Standard.
GenericConversion ::= OBJECT IDENTIFIER

--	The allocation of the Object Identifier values related to the EXTERNAL type is beyond the scope of this
--	Recommendation | International Standard.
GenericStrongCredentials ::= EXTERNAL

--	The allocation of the Object Identifier values related to the EXTERNAL type is beyond the scope of this
--	Recommendation | International Standard.
GenericMessageId ::= SEQUENCE {
  displayFormat  IA5String,
  typedFormat    EXTERNAL
}

--	The allocation of the Object Identifier values related to the EXTERNAL type is beyond the scope of this
--	Recommendation | International Standard.
GenericName ::= SEQUENCE {displayFormat  IA5String,
                          typedFormat    EXTERNAL
}

--	The allocation of the Object Identifier values related to the EXTERNAL type is beyond the scope of this 
--	Recommendation | International Standard.
HeldByManager ::= BOOLEAN --	Held is true, not held is false

InformationLossSuspected ::= BOOLEAN

--	Loss suspected is true, Loss not suspected is false
MprInfo ::=
  SET OF
    SEQUENCE {mprId            EMailMpduIdentifier,
              arrivalTime      Time,
              processingState  ProcessingState}

MtsUserType ::= INTEGER {ms(1), ua(2), au(3)}

NumberOfAssociations ::= INTEGER

ObjectIdOrDN ::= CHOICE {
  distinguishedName  DistinguishedName,
  oid                OBJECT IDENTIFIER
}

Percent ::= INTEGER(0..100)

PriorityList ::= SET OF Priority

ProcessingState ::= INTEGER {
  idle(0), processed(1), rejected(2), name-resolution(3), dl-expansion(4),
  redirection(5), deferred-delivery(6), conversion(7), securityContextCheck(8),
  unknownFunction(9)}

--	A processing state set to 'idle' indicates that the MPR is waiting to be processed. A processing state set to
--	'processed' indicates that the MPR was successfully processed. A processing state set to 'rejected' indicates that
--	the MTS was not able to deliver the message or the report or affirm the probe. A processing state set to
--	'name-resolution', 'redirection', 'deferred-delivery', 'conversion' or 'securityContextCheck' indicates that the MPR
--	is currently performing the corresponding function on the MPR. The value 'unknownFunction' indicates that
--	the MTA is currently performing a function on the MPR that is not name resolution, dl expansion, redirection, 
--	deferred-delivery, conversion or security Context Check.
ProcessingSummary ::= BIT STRING {
  idle(0), processed(1), rejected(2), name-resolution(3), dl-expansion(4),
  redirection(5), deferred-delivery(6), conversion(7), securityContextCheck(8)
}

--	at most one of idle, processed, and rejected bits shall be 'one':
--	-	idle bit 'one' means the MPR is waiting to be processed;
--	-	processed bit 'one' means the MPR was successfully processed;
--	-	rejected bit 'one' means that the MTS was not able to deliver the message or the report or affirm the probe;
--	-	idle, processed, and rejected bits 'zero' mean the MPR is currently under process.
--	A 'name-resolution', 'redirection', 'deferred-delivery', 'conversion' or 'securityContextCheck' bit one means the
--	corresponding function was successfully performed on the MPR. If idle bit is set to 'one' (MPR idle),
--	dl-expansion, redirection, deferred-delivery and conversion bits shall be set to 'zero'.
Restrictions ::= SET OF Restriction

SecurityLabels ::= SET OF SecurityLabel

SizeInOctets ::= INTEGER

TypeOfMpr ::= INTEGER {message(0), probe(1), report(2)}

END

-- Generated by Asnp, the ASN.1 pretty-printer of France Telecom R&D

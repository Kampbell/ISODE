-- Module CMIP-A-ABORT-Information (X.711:10/1997)
CMIP-A-ABORT-Information {joint-iso-itu-t ms(9) cmip(1) modules(0) aAbortUserInfo(2)}
DEFINITIONS ::=
BEGIN

--	Information carried in user-information parameter of A-ABORT
CMIPAbortInfo ::= SEQUENCE {
  abortSource  [0] IMPLICIT CMIPAbortSource,
  userInfo     [1]  EXTERNAL OPTIONAL
}

CMIPAbortSource ::= ENUMERATED {cmiseServiceUser(0), cmiseServiceProvider(1)}

END

-- Generated by Asnp, the ASN.1 pretty-printer of France Telecom R&D

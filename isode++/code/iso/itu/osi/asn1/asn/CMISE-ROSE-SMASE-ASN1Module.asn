-- Module CMISE-ROSE-SMASE-ASN1Module (X.727:03/1999)
CMISE-ROSE-SMASE-ASN1Module {joint-iso-itu-t ms(9) smi(3) part9(9) asn1Module(2) 0}
--ASN1.Version 1990,1994 CMISE-ROSE-SMASE-ASN1Module 
--{joint-iso-itu-t ms(9) smi(3) part9(9) asn1Module(2) 0 }
DEFINITIONS ::=
BEGIN

--EXPORTS everything
IMPORTS
  FunctionalUnitPackage
    FROM SMASE-A-ASSOCIATE-Information {joint-iso-itu-t ms(9) smo(0)
      asn1Modules(2) negotiationDefinitions(0) version1(1)}
  -- from Rec. X.701 | ISO/IEC 10040
  ObjectInstance
    FROM CMIP-1 {joint-iso-itu-t ms(9) cmip(1) modules(0) protocol(3)}
  FunctionalUnits, ProtocolVersion
    FROM CMIP-A-ASSOCIATE-Information {joint-iso-itu-t ms(9) cmip(1) 
      modules(0) aAssociateUserInfo(1)}; -- End of IMPORTS

--Value References
crsMObjectClass OBJECT IDENTIFIER ::=
  {joint-iso-ccitt ms(9) smi(3) part9(9) managedObjectClass(3)}

crsMPackage OBJECT IDENTIFIER ::=
  {joint-iso-ccitt ms(9) smi(3) part9(9) package(4)}

crsMNameBinding OBJECT IDENTIFIER ::=
  {joint-iso-ccitt ms(9) smi(3) part9(9) nameBinding(6)}

crsAttribute OBJECT IDENTIFIER ::=
  {joint-iso-ccitt ms(9) smi(3) part9(9) attribute(7)}

--Type References
CmipPduReceivingSupport ::= CmipPduType

CmipPduSendingSupport ::= CmipPduType

CmipPduType ::= BIT STRING {
  m-get-invoke(1), m-get-rors(2), m-get-linked-reply(3), m-set-invoke(4),
  m-setconf-invoke(5), m-setconf-rors(6), m-setconf-linked-reply(7),
  m-action-invoke(8), m-actionconf-invoke(9), m-actionconf-rors(10),
  m-actionconf-linked-reply(11), m-delete-invoke(12), m-delete-rors(13),
  m-delete-linked-reply(14), m-create-invoke(15), m-create-rors(16),
  m-eventReport-invoke(17), m-eventReportConf-invoke(18),
  m-eventReportConf-rors(19), m-cancelGet-invoke(20), m-cancelGet-rors(21),
  noSuchObjectClass-roer(22), noSuchObjectlnstance-roer(23),
  accessDenied-roer(24), syncNotSupported-roer(25), invalidFilter-roer(26),
  noSuchAttribute-roer(27), invalidAttributeValue-roer(28),
  getListError-roer(29), setListError-roer(30), noSuchAction-roer(31),
  processingfailure-roer(32), duplicateManagedObjectlnstance-roer(33),
  noSuchReferenceObject-roer(34), noSuchEventType-roer(35),
  noSuchArgument-roer(36), invalidArgumentValue-roer(37),
  invalidscope-roer(38), invalidObjectInstance-roer(39),
  missingAttributeValue-roer(40), classlnstanceConflict-roer(41),
  complexityLimitation-roer(42), misstypedOperation-roer(43),
  noSuchlnvokeID-roer(44), operationCanceled-roer(45), rosReject(46)}

CmiseFunctionalUnitsSelected ::= FunctionalUnits

CmiseFunctionalUnitsSupported ::= FunctionalUnits

InvokeldsOutstanding ::= SET OF INTEGER

InvokeIdsPerforming ::= SET OF INTEGER

MaxEncodedCmipPduReceiveSize ::= INTEGER(0..MAX) -- in bytes
                                        

ProtocolVersionSupported ::= ProtocolVersion

SmaseFunctionalUnits ::= SET OF FunctionalUnitPackage

SmUserInfoSent ::= CHOICE {
  nothingSent      NULL,
  informationSent  GraphicString
}

SmUserInfoReceived ::= CHOICE {
  nothingReceived      NULL,
  informationReceived  GraphicString
}

END -- of CMISE-ROSE-SMASE-ASN1Module 

-- Generated by Asnp, the ASN.1 pretty-printer of France Telecom R&D

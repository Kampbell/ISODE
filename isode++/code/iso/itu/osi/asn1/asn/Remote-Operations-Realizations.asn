-- Module Remote-Operations-Realizations (X.882:07/1994)

Remote-Operations-Realizations {joint-iso-itu-t remote-operations(4)
  realizations(9) version1(0)} DEFINITIONS ::=
BEGIN

-- exports everything
IMPORTS
  REALIZATION
    FROM Remote-Operations-Information-Objects-extensions {joint-iso-itu-t
      remote-operations(4) informationObjects-extensions(8) version1(0)};

RealizationParameter ::= SEQUENCE {
  realization-type  ENUMERATED {association-service(0), transfer-service(1)},
  concatenation     BOOLEAN DEFAULT FALSE
}

acse REALIZATION ::= {
  RealizationParameter
    (WITH COMPONENTS {
       realization-type  (association-service)
     })
  IDENTIFIED BY
    {joint-iso-itu-t remote-operations(4) association-realizations(10) acse-without-concatenation(0)}
}

acse-with-concatenation REALIZATION ::= {
  RealizationParameter
    (WITH COMPONENTS {
       realization-type  (association-service),
       concatenation     (TRUE)
     })
  IDENTIFIED BY
    {joint-iso-itu-t remote-operations(4) association-realizations(10) acse-with-concatenation(1)}
}

association-by-RTSE REALIZATION ::= {
  RealizationParameter
    (WITH COMPONENTS {
       realization-type  (association-service)
     })
  IDENTIFIED BY
    {joint-iso-itu-t remote-operations(4) association-realizations(10) association-by-rtse(2)}
}

pData REALIZATION ::= {
  RealizationParameter(WITH COMPONENTS {
                         realization-type  (transfer-service)
                       })
  IDENTIFIED BY
    {joint-iso-itu-t remote-operations(4) transfer-realizations(11)  pData-without-concatenation(0)}
}

pData-with-concatenation REALIZATION ::= {
  RealizationParameter
    (WITH COMPONENTS {
       realization-type  (transfer-service),
       concatenation     (TRUE)
     })
  IDENTIFIED BY
    {joint-iso-itu-t remote-operations(4) transfer-realizations(11) pData-with-concatenation(1)}
}

transfer-by-RTSE REALIZATION ::= {
  RealizationParameter(WITH COMPONENTS {
                         realization-type  (transfer-service)
                       })
  IDENTIFIED BY
    {joint-iso-itu-t remote-operations(4) transfer-realizations(11) rTSE-transfer(2)}
}

END -- end of the OSI realizations module

-- Generated by Asnp, the ASN.1 pretty-printer of France Telecom R&D

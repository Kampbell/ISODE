-- Module Remote-Operations-Abstract-Syntaxes (X.882:07/1994)

Remote-Operations-Abstract-Syntaxes {joint-iso-itu-t remote-operations(4)
  remote-operations-abstract-syntaxes(12) version1(0)} DEFINITIONS ::=
BEGIN

-- exports everything
IMPORTS
  OPERATION-PACKAGE
    FROM Remote-Operations-Information-Objects {joint-iso-itu-t remote-operations(4) informationObjects(5) version1(0)}
  InvokeId, noInvokeId, ROS{}, Bind{}, Unbind{}
    FROM Remote-Operations-Generic-ROS-PDUs {joint-iso-itu-t remote-operations(4) generic-ROS-PDUs(6) version1(0)}
  ACSE-apdu
    FROM ACSE-1 {joint-iso-itu-t association-control(2) modules(0) apdus(0) version1(1)}
  RTORQapdu, RTOACapdu, RTORJapdu
    FROM Reliable-Transfer-APDU {joint-iso-itu-t reliable-transfer(3) apdus(0)}
  combine{}, AllOperations{}, ConsumerPerforms{}, SupplierPerforms{}
    FROM Remote-Operations-Useful-Definitions {joint-iso-itu-t remote-operations(4) useful-definitions(7) version1(0)}
  APPLICATION-CONTEXT
    FROM Remote-Operations-Information-Objects-extensions {joint-iso-itu-t remote-operations(4) informationObjects-extensions(8) version1(0)};

RTSE-apdus ::= CHOICE {
  rtorq-apdu  [16] IMPLICIT RTORQapdu,
  rtoac-apdu  [17] IMPLICIT RTOACapdu,
  rtorj-apdu  [18] IMPLICIT RTORJapdu,
  rttp-apdu   RTTPapdu,
  rttr-apdu   RTTRapdu,
  rtab-apdu   [22] IMPLICIT RTABapdu
}

RTTPapdu ::= -- priority-- INTEGER

RTTRapdu ::= OCTET STRING

RTABapdu ::= SET {
  abortReason         [0] IMPLICIT AbortReason OPTIONAL,
  reflectedParameter  [1] IMPLICIT BIT STRING OPTIONAL,
  -- 8 bits maximum, only if abortReason is invalidParameter
  userdataAB
    [2]  TYPE-IDENTIFIER.&Type
      OPTIONAL -- only in normal mode and if abortReason--
  -- is userError 
}

AbortReason ::= INTEGER {
  localSystemProblem(0),
  invalidParameter(1), -- reflectedParameter supplied
  unrecognizedActivity(2),
  temporaryProblem(3),
  -- the RTSE cannot accept a session for a period of time
  protocolError(4), -- RTSE level protocol error
  permanentProblem(5), --provider-abort solely in normal mode 
  userError(6), -- user-abort solely in normal mode
  transferCompleted(7) -- activity can't be discarded--}

acse-abstract-syntax ABSTRACT-SYNTAX ::= {
  ACSE-apdu
  IDENTIFIED BY
    {joint-iso-itu-t association-control(2) abstract-syntax(1) apdus(0) version1(1)}
}

rtse-abstract-syntax ABSTRACT-SYNTAX ::= {
  RTSE-apdus
  IDENTIFIED BY  {joint-iso-itu-t reliable-transfer(3) apdus(0)}
}

AllValues{APPLICATION-CONTEXT:ac} ::= CHOICE {
  bind          Bind{ac.&associationContract.&connection.&bind},
  unbind        Unbind{ac.&associationContract.&connection.&unbind},
  ros-singleAS
    ROS-SingleAS{{ROSEInvokeIds},
                combine{{ac.&associationContract.&OperationsOf |
                       ac.&associationContract.&InitiatorConsumerOf |
                       ac.&associationContract.&ResponderConsumerOf}, {
                       ...},
                       {-- Information Object of class OPERATION-PACKAGE to be defined -- }}}
}

ROS-SingleAS{InvokeId:ROSEInvokeIds, OPERATION-PACKAGE:package} ::=
  ROS{{ROSEInvokeIds}, {AllOperations  {package}}, {AllOperations  {package}}}

ROS-ConsumerAS{InvokeId:ROSEInvokeIds, OPERATION-PACKAGE:package} ::=
  ROS
    {{ROSEInvokeIds}, {ConsumerPerforms  {package}},
    {SupplierPerforms  {package}}}

ROS-SupplierAS{InvokeId:ROSEInvokeIds, OPERATION-PACKAGE:package} ::=
  ROS
    {{ROSEInvokeIds}, {SupplierPerforms  {package}},
    {ConsumerPerforms  {package}}}

ROSEInvokeIds InvokeId ::= {ALL EXCEPT noInvokeId}

END -- end of the remote-operations-abstract-syntaxes module

-- Generated by Asnp, the ASN.1 pretty-printer of France Telecom R&D
